# R-LFAST_FUNCTIONAL

## R-LFAST-2xx: Range of Travel (Functional)
- Rationale: Each Unit Telescope shall be capable of a full range of travel in elevation from -20deg below horizontal to 95deg elevation angle. The azimuth range of rotation shall be 540deg 土270deg either side of north.
  Verification by: Demonstration / Analysis / Inspection / Test
  Rationale: Travel range needed for telescope design to ensure structure is capable of required orientation range
  Comment: Discussed at controls meeting with Ford/Chavez/Angel 20220309

## R-LFAST-2xx: Elevation Slew and Tracking Speeds (Functional)
- Rationale: The EL drive shall be capable of slewing the telescope from horizon to zenith in 2 minutes. This requires drive motor rotation speed of 1875 rpm, assuming the 15,000:1 gearing ratio
  Verification by: Demonstration / Analysis / Inspection / Test
  Rationale: Needed to design drive motors and control electronics.

## R-LFAST-2xx: Imaging Performance (Functional)
- Rationale: Each telescope shall deliver an imaging performance of better than 0.5 arcsec FWHM, consisting of equal error contributions from mirror figure, mirror support, thermal effects and mount tracking, optical design error, etc.
  Verification by: Demonstration / Analysis / Inspection / Test
  Rationale: Roger’s assumptions

### #5: L4 Image Translation Scale (Functional)
- Rationale: For every 1 mm lateral shift of L4, the chief ray height difference at the image plane changes by 36.7 μm, which corresponds to 2.87 arcseconds, and the relationship of lens translation to induced lateral chromatic aberration is linear

## #6: Az/El Tracking Accuracy 1sigma (Functional)
- Rationale: The Az/El slew drives must be able to maintain a 1sigma tracking accuracy spec of TBD
  (pending error budget)
